FME workspace QGISFMEFormConnectorTemplate.fmw

Parameters:
- myCoef = 5   # Enter Numeric Data
- SourceDataset_GEOJSON = C:\Users\lyesm\AppData\Roaming\QGIS\QGIS3\profiles\default\temp\20250408_vfcrh_line2_input.geojson   # Source GeoJSON File or URL
- FEATURE_TYPES =
- DestDataset_GEOJSON =   # Destination GeoJSON File
- OFFSET =   # Buffer Distance

Readers:
- GEOJSON_1: GEOJSON from $(SourceDataset_GEOJSON)

Writers:
- GEOJSON_2: GEOJSON to $(DestDataset_GEOJSON)

Note: GeoJson File Generated by QGIS
Note: Any Transformers

Bookmark: GeoJson File Generated by QGIS
20250408_vfcrh_line2_input (reader GEOJSON_1)
    attributes: id int, Points int
    -> Counter

Bookmark: Any Transformers
Counter
    CNT_ATTR = _count
    DOMAIN = counter
    SCOPE = Global
    START = 0
    -> AttributeManager
AttributeManager
    ATTR_TABLE = SET_TO name (varchar(200)) = @round(@DateTimeNow(),0)converted_data
    USER_EXPOSED_ATTRIBUTES = _newCount,name
    -> Bufferer
Bufferer
    ANGLE = 22.5
    CAP_STYLE_LOOKUP = CAP_ARC
    CORNER_STYLE_LOOKUP = JOIN_ARC
    MODE = AREA
    OFFSET = $(OFFSET)
    OFFSET_UNITS = NONE
    PRECISION = APPROX
    CAP_STYLE = Arc
    CORNER_STYLE = Arc
    BUFFERED -> NewFeatureType (writer GEOJSON_2)

Bookmark: GeoJson File
Note: GeoJSON fileto be Uploaded by QGIS as a Layer
NewFeatureType (writer GEOJSON_2)
    attributes: _count int, name string, id int, Points int
